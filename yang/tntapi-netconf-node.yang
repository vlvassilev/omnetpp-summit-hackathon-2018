module tntapi-netconf-node {

  namespace
    "urn:tntapi:netconf-node";
  prefix "netconf-node";

  import "ietf-network" { prefix nd; }

  organization
    "tntapi project";

  contact
    "Vladimir Vassilev <mailto:vladimir@transpacket.com>";

  description
    "This module augments ietf-network with data nodes
     for management of NETCONF enabled nodes.";

  revision 2018-08-29 {
    description
      "Initial version.";
  }

  augment "/nd:networks/nd:network/nd:node" {
    description
      "Adds extra parameters for accessing netconf enabled nodes.";

    anyxml data {
      description
        "Operational data of the node containing all top level nodes.";
    }
    anyxml config {
      description
        "Configuration data of the node containing all top level nodes.";
    }

    container netconf-connect-params {
      description
        "Parameters for connecting to netconf managed device.";

      presence "This node is accessible for netconf management.";

      leaf user {
        description
          "User name to use for NETCONF sessions.";
        type string;
      }

      leaf server {
        description
          "IP address or DNS name of the NETCONF server target.";
        type string;
      }

      leaf password {
        description
          "User password to use for NETCONF sessions.
           If none, then user will be prompted before connecting.";
        type string;
      }

      leaf ncport {
        description 
          "NETCONF port number to use.  If not present, then
           port 830, followed by port 22, will be tried.";
        type uint16 {
          range "1..max";
        }
        default 830;
      }
      leaf public-key {
        type string {
          length "1 .. max";
        }
        description
          "Contains the file path specification
           for the file containing the client-side public key.
           If both 'public-key' and 'private-key' files are
           present, the client will attempt to connect
           to the server using these keys.  If this fails,
           or not done, then password authentication will
           be attempted.";
          default "$HOME/.ssh/id_rsa.pub";
        }

      leaf private-key {
        type string {
          length "1 .. max";
        }
        description
          "Contains the file path specification
           for the file containing the client-side private key.
           If both 'public-key' and 'private-key' files are
           present, the client will attempt to connect
           to the server using these keys.  If this fails,
           or not done, then password authentication will
           be attempted.";
        default "$HOME/.ssh/id_rsa";
      }
    }
  }
}
